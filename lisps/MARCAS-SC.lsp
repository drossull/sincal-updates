;;; Marcas de armadura: tabla A=marca B=cantidad C=diametro D=separacion.
;;; Windows / AutoCAD ActiveX. No carga ni altera dibujos al cargar este archivo.
;;; Los campos nativos actualizan valores; ACTUALIZAR-MARCAS repara su direccion
;;; a partir del ID guardado en la celda A (no del numero visible de marca).
(vl-load-com)

(defun SCM:Fail (message) (princ (strcat "\nMARCAS-SC: " message)) (quit))
(defun SCM:Doc () (vla-get-ActiveDocument (vlax-get-acad-object)))
(defun SCM:Trim (s) (vl-string-trim " \t\r\n" s))
(defun SCM:MarkKey (s) (strcase (SCM:Trim s)))
(defun SCM:ValidMark (s / i n)
  ;; Digits followed by an optional ASCII letter suffix: 5, 5a, 12AB.
  ;; Keep the original spelling for display; never convert the mark to a number.
  (setq s (SCM:MarkKey s) i 1 n (strlen s))
  (while (and (<= i n) (wcmatch (substr s i 1) "[0-9]"))
    (setq i (1+ i)))
  (and (> i 1)
    (progn
      (while (and (<= i n) (wcmatch (substr s i 1) "[A-Z]"))
        (setq i (1+ i)))
      (> i n))))
(defun SCM:Locked (obj)
  (= :vlax-true (vla-get-Lock (vla-item (vla-get-Layers (SCM:Doc)) (vla-get-Layer obj)))))
(defun SCM:Attrs (obj / a out)
  (if (= :vlax-true (vla-get-HasAttributes obj))
    (foreach a (vlax-invoke obj 'GetAttributes)
      (setq out (cons (cons (strcase (vla-get-TagString a)) a) out))))
  out)
(defun SCM:MarkP (obj / attrs)
  (and (= "AcDbBlockReference" (vla-get-ObjectName obj))
       (setq attrs (SCM:Attrs obj)) (assoc "XX" attrs) (assoc "MARCA" attrs)))
(defun SCM:DetailP (obj / attrs)
  (setq attrs (SCM:Attrs obj))
  (and (assoc "CANT_TOTAL" attrs) (assoc "LARGO" attrs)))
(defun SCM:DetailEditableP (obj / attrs)
  (setq attrs (SCM:Attrs obj))
  (or (not (SCM:DetailP obj))
    (and (= :vlax-false (vla-get-MTextAttribute (cdr (assoc "CANT_TOTAL" attrs))))
         (= :vlax-false (vla-get-MTextAttribute (cdr (assoc "LARGO" attrs)))))))
(defun SCM:MakeDetailEditable (obj / attrs tag att value)
  ;; Convert only manual attributes on this reference, preserving their values.
  ;; No ATTSYNC/redefinition: those can reset user values and dynamic settings.
  (if (SCM:DetailP obj)
    (progn
      (setq attrs (SCM:Attrs obj))
      (foreach tag '("CANT_TOTAL" "LARGO")
        (setq att (cdr (assoc tag attrs)))
        (if (= :vlax-true (vla-get-MTextAttribute att))
          (progn
            (setq value (vla-get-TextString att) SCM:changed T)
            (vla-put-MTextAttribute att :vlax-false)
            (vla-put-TextString att value)
            (vla-Update att)))))))
(defun SCM:WritableMark (obj / a)
  (if (not (SCM:MarkP obj)) (SCM:Fail "El bloque necesita atributos editables XX y MARCA."))
  (if (SCM:Locked obj) (SCM:Fail "La capa del bloque esta bloqueada."))
  (foreach a (SCM:Attrs obj)
    (if (and (member (car a) '("XX" "MARCA" "MARCA_CANT" "CANT_TOTAL" "LARGO")) (SCM:Locked (cdr a)))
      (SCM:Fail "La capa de un atributo esta bloqueada.")))
  obj)
(defun SCM:TableP (obj)
  (and (= "AcDbTable" (vla-get-ObjectName obj))
       (= 4 (vla-get-Columns obj)) (> (vla-get-Rows obj) 2)
       (= "MARCA" (strcase (SCM:Trim (vla-GetText obj 1 0))))))
(defun SCM:PickTable (/ picked obj)
  (setq picked (entsel "\nSeleccione tabla (A=marca, B=cantidad, C=diametro, D=separacion): "))
  (if (not picked) (quit))
  (setq obj (vlax-ename->vla-object (car picked)))
  (if (not (SCM:TableP obj))
    (SCM:Fail "Se requiere tabla de 4 columnas, titulo en fila 1 y MARCA en A2."))
  (if (SCM:Locked obj) (SCM:Fail "La capa de la tabla esta bloqueada."))
  (if (not (vlax-method-applicable-p obj 'SetCustomData))
    (SCM:Fail "Este motor CAD no admite identificadores por celda."))
  obj)
(defun SCM:RowByMark (table mark / row matches)
  (setq row 2)
  (while (< row (vla-get-Rows table))
    (if (= (SCM:MarkKey mark) (SCM:MarkKey (vla-GetText table row 0)))
      (setq matches (cons row matches)))
    (setq row (1+ row)))
  (if (/= (length matches) 1)
    (SCM:Fail "La marca no existe o esta repetida en la tabla."))
  (car matches))
(defun SCM:PickRow (table / mark row)
  (setq mark (SCM:Trim (getstring T "\nMarca en la tabla (ej. 5, 5a): ")))
  (if (= mark "") (quit))
  (setq row (SCM:RowByMark table mark))
  row)
(defun SCM:RowIssue (table row) (SCM:RowIssueFor table row nil))
(defun SCM:RowIssueFor (table row detail / mark r matches diameter spacing quantity)
  (setq mark (SCM:Trim (vla-GetText table row 0)) r 2 matches 0
        quantity (distof (SCM:Trim (vla-GetText table row 1)) 2)
        diameter (distof (SCM:Trim (vla-GetText table row 2)) 2)
        spacing (distof (SCM:Trim (vla-GetText table row 3)) 2))
  (while (< r (vla-get-Rows table))
    (if (= (SCM:MarkKey mark) (SCM:MarkKey (vla-GetText table r 0))) (setq matches (1+ matches)))
    (setq r (1+ r)))
  (cond
    ((not (SCM:ValidMark mark))
      "Use digitos con un sufijo opcional de letras A-Z (ej. 5, 5a, 12AB), sin espacios internos ni formulas.")
    ((> matches 1) "Marca duplicada en la tabla (no se distinguen mayusculas/minusculas).")
    ((and (not detail) (not (and quantity (> quantity 0.0) (= quantity (fix quantity)))))
      "Cantidad debe ser un entero positivo.")
    ((not (and diameter (> diameter 0.0))) "Diametro debe ser un numero positivo.")
    ((and (not detail) (not (and spacing (> spacing 0.0))))
      "Separacion debe ser un numero positivo.")))
(defun SCM:RowID (table row / value result)
  (setq result (vl-catch-all-apply 'vla-GetCustomData (list table row 0 "SINCAL_MARCA_ID_V1" 'value)))
  (if (not (vl-catch-all-error-p result))
    (progn
      (if (= (type value) 'VARIANT) (setq value (vlax-variant-value value)))
      (if (= (type value) 'STR) value))))
(defun SCM:RowsByID (table id / row matches)
  (setq row 2)
  (while (< row (vla-get-Rows table))
    (if (equal id (SCM:RowID table row)) (setq matches (cons row matches)))
    (setq row (1+ row)))
  matches)
(defun SCM:EnsureID (table row / id serial)
  (setq id (SCM:RowID table row))
  (if (and id (/= (length (SCM:RowsByID table id)) 1))
    (SCM:Fail "ID de fila duplicado; no es seguro elegir una fila."))
  (if (not id)
    (progn
      (setq serial 0 id (strcat "SC-" (vla-get-Handle table) "-"
        (rtos (getvar "CDATE") 2 8) "-" (itoa (getvar "MILLISECS")) "-" (itoa row)))
      (while (SCM:RowsByID table id)
        (setq serial (1+ serial) id (strcat id "-" (itoa serial))))
      (vla-SetCustomData table row 0 "SINCAL_MARCA_ID_V1" (vlax-make-variant id vlax-vbString))
      (setq SCM:changed T)))
  id)
(defun SCM:DocumentID (create / record id en)
  (setq record (dictsearch (namedobjdict) "SINCAL_MARCA_DOCUMENT_V1"))
  (if record (cdr (assoc 1 record))
    (if create
      (progn
        (setq id (strcat "SC-DOC-" (rtos (getvar "CDATE") 2 8) "-"
                        (itoa (getvar "MILLISECS")) "-" (vl-princ-to-string (namedobjdict))))
        (setq en (entmakex (list '(0 . "XRECORD") '(100 . "AcDbXrecord") '(280 . 1) (cons 1 id))))
        (if (not (and en (dictadd (namedobjdict) "SINCAL_MARCA_DOCUMENT_V1" en)))
          (SCM:Fail "No se pudo registrar la identidad del dibujo."))
        (setq SCM:changed T)
        id))))
(defun SCM:Metadata (obj / data values strings handle en docid)
  (setq data (assoc -3 (entget (vlax-vla-object->ename obj) '("SINCAL_MARCA_V1"))))
  (if data
    (progn
      (setq values (cdadr data))
      (if (= 1 (cdr (assoc 1070 values)))
        (progn
          (setq strings (mapcar 'cdr (vl-remove-if-not '(lambda (p) (= 1000 (car p))) values))
                handle (cdr (assoc 1005 values)))
          ;; COPYCLIP elimina handles 1005 de objetos no copiados. El respaldo
          ;; solo es valido en el mismo DWG, nunca por numero de marca en otro.
          (if (and (not (and handle (setq en (handent handle)) (entget en)))
                   (setq docid (SCM:DocumentID nil))
                   (equal (nth 2 strings) docid) (nth 3 strings))
            (setq handle (nth 3 strings)))
          (list handle (car strings)))))))
(defun SCM:LastMark (obj / data strings)
  (setq data (assoc -3 (entget (vlax-vla-object->ename obj) '("SINCAL_MARCA_V1"))))
  (if data
    (progn (setq strings (vl-remove-if-not '(lambda (p) (= 1000 (car p))) (cdadr data)))
      (cdr (cadr strings)))))
(defun SCM:Store (obj table id / en rows mark)
  (regapp "SINCAL_MARCA_V1")
  (setq en (vlax-vla-object->ename obj))
  (setq rows (SCM:RowsByID table id) mark (SCM:Trim (vla-GetText table (car rows) 0)))
  (if (not (entmod (append (entget en)
    (list (list -3 (list "SINCAL_MARCA_V1" '(1070 . 1)
      (cons 1005 (vla-get-Handle table)) (cons 1000 id) (cons 1000 mark)
      (cons 1000 (SCM:DocumentID T)) (cons 1000 (vla-get-Handle table))))))))
    (SCM:Fail "No se pudo guardar el vinculo del bloque.")))
(defun SCM:FieldFormat (col)
  (strcat "%lu2%pr" (if (= col "B") "0" "1") "%zs8"))
(defun SCM:Field (table row col / oid)
  (setq oid (vla-GetObjectIdString (vla-get-Utility (SCM:Doc)) table :vlax-false))
  (strcat "%<\\AcExpr (Table(%<\\_ObjId " oid ">%)." col (itoa (1+ row))
    ") \\f \"" (SCM:FieldFormat col) "\">%"))
(defun SCM:PutText (att text)
  (vla-put-TextString att text)
  (if (= :vlax-true (vla-get-MTextAttribute att))
    (vla-UpdateMTextAttribute att)))
(defun SCM:Bind (obj table row / attrs id issue description)
  (SCM:WritableMark obj)
  (if (SCM:Locked table) (SCM:Fail "La capa de la tabla esta bloqueada."))
  (if (setq issue (SCM:RowIssueFor table row (SCM:DetailP obj))) (SCM:Fail issue))
  (SCM:MakeDetailEditable obj)
  (setq id (SCM:EnsureID table row) attrs (SCM:Attrs obj))
  ;; XX es una entrada editable, no un campo. Su ultimo valor se conserva en XData.
  (SCM:PutText (cdr (assoc "XX" attrs)) (SCM:Trim (vla-GetText table row 0)))
  (setq SCM:changed T)
  (setq description (strcat "%%c" (SCM:Field table row "C")
    (if (SCM:DetailP obj) "" (strcat "@" (SCM:Field table row "D")))))
  (SCM:PutText (cdr (assoc "MARCA" attrs)) description)
  (if (assoc "MARCA_CANT" attrs)
    (SCM:PutText (cdr (assoc "MARCA_CANT" attrs)) (strcat (SCM:Field table row "B") " " description)))
  (SCM:Store obj table id)
  (vla-Update obj)
  obj)
;;; Resuelve solo por identidad. Nunca adivina otra fila por el valor visible.
;;; Devuelve (tabla fila) o un mensaje de diagnostico.
(defun SCM:Resolve (obj / meta en table rows issue)
  (cond
    ((not (setq meta (SCM:Metadata obj))) "Sin registro SINCAL: use REASIGNAR-MARCA para vincular.")
    ((not (and (setq en (handent (car meta))) (entget en))) "Tabla de origen ausente.")
    ((not (SCM:TableP (setq table (vlax-ename->vla-object en)))) "Tabla de origen incompatible.")
    ((not (setq rows (SCM:RowsByID table (cadr meta)))) "Fila eliminada o sin ID.")
    ((/= 1 (length rows)) "ID duplicado: fila ambigua.")
    ((setq issue (SCM:RowIssueFor table (car rows) (SCM:DetailP obj))) issue)
    (T (list table (car rows)))))
;;; Obtiene los campos reales sin crear diccionarios al revisar.
(defun SCM:Fields (en / ed pair out)
  (setq ed (entget en))
  (if (= "FIELD" (cdr (assoc 0 ed))) (setq out (list ed)))
  (foreach pair ed
    (if (member (car pair) '(350 360))
      (setq out (append out (SCM:Fields (cdr pair))))))
  out)
(defun SCM:AttributeMatches (att table row columns / records expressions record code col good refs expected)
  (setq records (SCM:Fields (vlax-vla-object->ename att)))
  (foreach record records
    (if (= "AcExpr" (cdr (assoc 1 record))) (setq expressions (cons record expressions))))
  (setq good (= (length expressions) (length columns)))
  (foreach col columns
    (setq expected (strcat "\\AcExpr (Table(%<\\_ObjIdx 0>%)." col (itoa (1+ row))
      ") \\f \"" (SCM:FieldFormat col) "\"") refs 0)
    (foreach record expressions
      (if (and (= expected (cdr (assoc 2 record)))
               (equal (cdr (assoc 331 record)) (vlax-vla-object->ename table)))
        (setq refs (1+ refs))))
    (if (/= refs 1) (setq good nil)))
  ;; Valida tambien el texto envolvente para detectar ediciones manuales.
  (setq code (cdr (assoc 2 (car records))))
  (and good (equal code (cond
    ((equal columns '("A")) "%<\\_FldIdx 0>%")
    ((equal columns '("C")) "%%c%<\\_FldIdx 0>%")
    ((equal columns '("B" "C" "D")) "%<\\_FldIdx 0>% %%c%<\\_FldIdx 1>%@%<\\_FldIdx 2>%")
    (T "%%c%<\\_FldIdx 0>%@%<\\_FldIdx 1>%")))))
(defun SCM:Healthy (obj binding / attrs)
  (setq attrs (SCM:Attrs obj))
  (and (SCM:DetailEditableP obj)
       (equal (SCM:Trim (vla-get-TextString (cdr (assoc "XX" attrs))))
              (SCM:Trim (vla-GetText (car binding) (cadr binding) 0)))
       (SCM:AttributeMatches (cdr (assoc "MARCA" attrs)) (car binding) (cadr binding)
         (if (SCM:DetailP obj) '("C") '("C" "D")))
       (or (not (assoc "MARCA_CANT" attrs))
           (SCM:AttributeMatches (cdr (assoc "MARCA_CANT" attrs)) (car binding) (cadr binding) '("B" "C" "D")))))
(defun SCM:Selected (/ ss i obj out)
  (princ "\nSeleccione bloques de marca: ")
  (setq ss (ssget '((0 . "INSERT"))))
  (if (not ss) (quit))
  (setq i 0)
  (repeat (sslength ss)
    (setq obj (vlax-ename->vla-object (ssname ss i)) i (1+ i))
    (SCM:WritableMark obj)
    (setq out (cons obj out)))
  out)
(defun SCM:Evaluate (objects / ss obj)
  (setq ss (ssadd))
  (foreach obj objects (ssadd (vlax-vla-object->ename obj) ss))
  (if (> (sslength ss) 0) (vl-cmdf "_.UPDATEFIELD" ss ""))
  (vla-Regen (SCM:Doc) 1))
;;; Un grupo UNDO por comando; ante error/cancelacion revierte solo este grupo.
(defun SCM:Run (fn / *error* started SCM:changed SCM:busy)
  (setq SCM:busy T)
  (defun *error* (message)
    (if started
      (progn (command-s "_.UNDO" "_End") (if SCM:changed (command-s "_.U"))))
    (if (and message (not (wcmatch (strcase message) "*CANCEL*,*QUIT*,*BREAK*,*EXIT ABORT*")))
      (princ (strcat "\n" message)))
    (princ))
  (if (= 0 (logand 1 (getvar "UNDOCTL")))
    (SCM:Fail "Active UNDO antes de ejecutar este comando."))
  (command "_.UNDO" "_Begin")
  (setq started T)
  (apply fn nil)
  (command "_.UNDO" "_End")
  (setq started nil)
  (princ))
;;; La definicion nativa contiene flip, visibilidad, RomanD y mascara MText.
(defun SCM:TemplatePath () (SCM:TemplateNamed "SINCAL_MARCA_SC_V2"))
(defun SCM:TemplateNamed (name / bases base candidate path)
  (setq bases (list
    (if (getenv "LOCALAPPDATA") (strcat (getenv "LOCALAPPDATA") "/SINCAL/resources"))
    (if (getenv "APPDATA") (strcat (getenv "APPDATA") "/Estandar SINCAL"))
    (if (getenv "ProgramFiles") (strcat (getenv "ProgramFiles") "/SINCAL"))
    (getenv "SINCAL_TEST_ROOT")))
  (foreach base bases
    (if (and base (not path) (setq candidate (findfile (strcat base "/masters/" name ".dwg"))))
      (setq path candidate)))
  (if (not path) (setq path (findfile (strcat name ".dwg"))))
  (if (not path)
    (setq path (getfiled (strcat "Seleccione masters/" name ".dwg") (strcat name ".dwg") "dwg" 0)))
  path)
(defun SCM:BasicDefinition () (SCM:DefinitionNamed "SINCAL_MARCA_SC_V2"))
(defun SCM:DefinitionNamed (name / path temp en)
  (if (not (tblsearch "BLOCK" name))
    (progn
      (setq path (SCM:TemplateNamed name))
      (if (not path) (SCM:Fail "No se encontro la plantilla dinamica."))
      (setq temp (vla-InsertBlock (vla-get-ModelSpace (SCM:Doc)) (vlax-3d-point '(0 0 0)) path 1.0 1.0 1.0 0.0)
            SCM:changed T)
      (vla-Delete temp)
      (if (not (tblsearch "BLOCK" name)) (SCM:Fail (strcat "La plantilla seleccionada no es " name ".dwg.")))
      (regapp "AcadAnnotative")
      (setq en (vlax-vla-object->ename (vla-item (vla-get-Blocks (SCM:Doc)) name)))
      (entmod (append (entget en)
        '((-3 ("AcadAnnotative" (1000 . "AnnotativeData") (1002 . "{")
              (1070 . 1) (1070 . 1) (1002 . "}"))))))))
  name)
(defun SCM:Insert () (SCM:InsertKind nil))
(defun SCM:InsertDetail () (SCM:InsertKind T))
(defun SCM:InsertKind (detail / table row pick proto point height obj space quantity lengthvalue issue)
  (setq table (SCM:PickTable) row (SCM:PickRow table))
  (if (setq issue (SCM:RowIssueFor table row detail)) (SCM:Fail issue))
  (setq pick (entsel "\nSeleccione una marca modelo, o Enter para bloque dinamico anotativo SINCAL: "))
  (if pick
    (progn
      (setq proto (SCM:WritableMark (vlax-ename->vla-object (car pick))))
      (if (not (eq (not (SCM:DetailP proto)) (not detail)))
        (SCM:Fail "Seleccione un modelo del mismo tipo: vista para MARCA-SC, despiece para MARCA-DE."))
      (if (/= (cdr (assoc 410 (entget (car pick)))) (if (= 1 (getvar "CVPORT")) (getvar "CTAB") "Model"))
        (SCM:Fail "El modelo debe estar en el espacio actual.")))
    (progn (initget 6) (setq height (getreal "\nAltura de texto en papel <2.5>: "))
      (if (not height) (setq height 2.5))))
  (if detail
    (progn
      (initget 7) (setq quantity (getint "\nCantidad total de la estructura (editable): "))
      (setq lengthvalue (SCM:Trim (getstring T "\nLargo del fierro, sin conversion de unidades (editable): ")))
      (if (not (and (distof lengthvalue 2) (> (distof lengthvalue 2) 0.0)))
        (SCM:Fail "El largo debe ser un numero positivo."))))
  (setq point (getpoint "\nPunto de insercion: "))
  (if (not point) (quit))
  (setq point (trans point 1 0))
  (if proto
    (progn (setq obj (vla-Copy proto) SCM:changed T)
      (vla-Move obj (vla-get-InsertionPoint obj) (vlax-3d-point point)))
    (progn
      (if (= :vlax-true (vla-get-Lock (vla-item (vla-get-Layers (SCM:Doc)) (getvar "CLAYER"))))
        (SCM:Fail "La capa actual esta bloqueada."))
      (setq space (if (= 1 (getvar "CVPORT")) (vla-get-PaperSpace (SCM:Doc)) (vla-get-ModelSpace (SCM:Doc))))
      (setq obj (vla-InsertBlock space (vlax-3d-point point)
        (SCM:DefinitionNamed (if detail "SINCAL_MARCA_DE_V1" "SINCAL_MARCA_SC_V2")) height height height 0.0)
            SCM:changed T)))
  (if detail
    (progn
      (SCM:PutText (cdr (assoc "CANT_TOTAL" (SCM:Attrs obj))) (itoa quantity))
      (SCM:PutText (cdr (assoc "LARGO" (SCM:Attrs obj))) (strcat "L=" lengthvalue))))
  (SCM:Bind obj table row)
  (SCM:Evaluate (list obj))
  (princ "\nMarca vinculada. Edite XX para cambiar de marca en la misma tabla; confirme la edicion."))
(defun SCM:Reassign (/ objects table row obj)
  (setq objects (SCM:Selected) table (SCM:PickTable) row (SCM:PickRow table))
  (foreach obj objects (SCM:Bind obj table row))
  (SCM:Evaluate objects)
  (princ (strcat "\nMarcas vinculadas: " (itoa (length objects)) ".")))
(defun SCM:Refresh (/ objects obj binding good skipped)
  (setq objects (SCM:Selected) skipped 0)
  (foreach obj objects
    (setq binding (SCM:Resolve obj))
    (if (= (type binding) 'STR)
      (progn (setq skipped (1+ skipped))
        (princ (strcat "\n" (vla-get-Handle obj) ": " binding)))
      (progn (SCM:Bind obj (car binding) (cadr binding)) (setq good (cons obj good)))))
  (SCM:Evaluate good)
  (princ (strcat "\nActualizadas: " (itoa (length good)) "; omitidas: " (itoa skipped) ".")))
(defun c:MARCA-SC () (SCM:Run 'SCM:Insert))
(defun c:MARCA-DE () (SCM:Run 'SCM:InsertDetail))
(defun c:REASIGNAR-MARCA () (SCM:Run 'SCM:Reassign))
(defun c:ACTUALIZAR-MARCAS () (SCM:Run 'SCM:Refresh))
(defun c:REVISAR-MARCAS (/ ss i obj binding total problems)
  (setq ss (ssget "_X" '((0 . "INSERT"))) i 0 total 0 problems 0)
  (if ss
    (repeat (sslength ss)
      (setq obj (vlax-ename->vla-object (ssname ss i)) i (1+ i))
      (if (SCM:MarkP obj)
        (progn
          (setq total (1+ total) binding (SCM:Resolve obj))
          (if (or (= (type binding) 'STR) (not (SCM:Healthy obj binding)))
            (progn
              (setq problems (1+ problems))
              (princ (strcat "\n" (vla-get-Handle obj) ": "
                (if (= (type binding) 'STR) binding "Campos alterados o fila desplazada: use ACTUALIZAR-MARCAS.")))))))))
  (princ (strcat "\nMarcas revisadas: " (itoa total) "; requieren atencion: " (itoa problems) "."))
  (princ))
;;; Los callbacks de objeto solo marcan trabajo pendiente. Nunca escriben en
;;; el objeto que AutoCAD esta notificando ni ejecutan comandos interactivos.
(defun SCM:Managed (/ layout obj out)
  (vlax-for layout (vla-get-Layouts (SCM:Doc))
    (vlax-for obj (vla-get-Block layout)
      (if (and (= "AcDbBlockReference" (vla-get-ObjectName obj))
               (SCM:Metadata obj) (SCM:MarkP obj))
        (setq out (cons obj out)))))
  out)
(defun SCM:OnObjectChanged (owner reactor params)
  (if (not SCM:busy) (setq SCM:pending T)))
(defun SCM:Watch (/ owners obj att meta en)
  (if SCM:objects (vlr-remove SCM:objects))
  (setq SCM:objects nil)
  (foreach obj (SCM:Managed)
    (setq owners (cons obj owners))
    (foreach att (SCM:Attrs obj) (setq owners (cons (cdr att) owners)))
    (setq meta (SCM:Metadata obj))
    (if (and (setq en (handent (car meta))) (entget en))
      (setq owners (cons (vlax-ename->vla-object en) owners))))
  (if owners
    (setq SCM:objects (vlr-object-reactor owners "SINCAL marcas"
      '((:vlr-modified . SCM:OnObjectChanged) (:vlr-erased . SCM:OnObjectChanged))))))
(defun SCM:ClearDescription (obj reason / att changed)
  (foreach att (SCM:Attrs obj)
    (if (and (member (car att) '("MARCA" "MARCA_CANT"))
             (not (SCM:Locked (cdr att)))
             (/= "[SIN VINCULO]" (vla-get-TextString (cdr att))))
      (progn (SCM:PutText (cdr att) "[SIN VINCULO]") (setq changed T))))
  (if changed (princ (strcat "\nMarca " (vla-get-Handle obj) ": " reason)))
  changed)
(defun SCM:SyncOne (obj / attrs mark previous meta en table row rows issue binding locked att)
  (setq attrs (SCM:Attrs obj) meta (SCM:Metadata obj)
        mark (SCM:Trim (vla-get-TextString (cdr (assoc "XX" attrs))))
        previous (SCM:LastMark obj) locked (SCM:Locked obj))
  (foreach att attrs (if (SCM:Locked (cdr att)) (setq locked T)))
  (cond
    (locked nil)
    ((not (and (setq en (handent (car meta))) (entget en)))
      (SCM:ClearDescription obj "Tabla de origen ausente."))
    ((not (SCM:TableP (setq table (vlax-ename->vla-object en))))
      (SCM:ClearDescription obj "Tabla de origen incompatible."))
    ((SCM:Locked table) nil)
    ((and previous (/= mark previous))
      (setq row 2)
      (while (< row (vla-get-Rows table))
        (if (= (SCM:MarkKey mark) (SCM:MarkKey (vla-GetText table row 0))) (setq rows (cons row rows)))
        (setq row (1+ row)))
      (cond
        ((/= 1 (length rows)) (SCM:ClearDescription obj "Marca inexistente o duplicada en la tabla."))
        ((setq issue (SCM:RowIssueFor table (car rows) (SCM:DetailP obj))) (SCM:ClearDescription obj issue))
        (T (SCM:Bind obj table (car rows)) T)))
    ((= 'STR (type (setq binding (SCM:Resolve obj)))) (SCM:ClearDescription obj binding))
    ((not (SCM:Healthy obj binding)) (SCM:Bind obj (car binding) (cadr binding)) T)))
(defun SCM:Sync (/ SCM:busy obj result changed)
  (setq SCM:busy T)
  (foreach obj (SCM:Managed)
    (setq result (vl-catch-all-apply 'SCM:SyncOne (list obj)))
    (if (vl-catch-all-error-p result)
      (princ (strcat "\nMARCAS-SC: " (vl-catch-all-error-message result)))
      (if result (setq changed T))))
  (if (or changed SCM:pending) (vl-catch-all-apply 'vla-Regen (list (SCM:Doc) 1)))
  (setq SCM:pending nil)
  (SCM:Watch))
(defun SCM:CommandEnded (reactor params / name result)
  (setq name (strcase (car params)))
  (if (and (not SCM:busy) (= 0 (getvar "BLOCKEDITOR")))
    (cond
      ((member name '("U" "UNDO" "REDO" "MREDO" "OOPS"))
        (setq SCM:pending nil) (SCM:Watch))
      ((or SCM:pending (wcmatch name "COPY*,PASTE*,*INSERT,*ATTEDIT*,REGEN*,CHPROP,CHANGE,GRIP*,*TABLE*,MARCA-SC,MARCA-DE,REASIGNAR-MARCA,ACTUALIZAR-MARCAS"))
        (setq result (vl-catch-all-apply 'SCM:Sync nil))
        (if (vl-catch-all-error-p result)
          (princ (strcat "\nMARCAS-SC: " (vl-catch-all-error-message result))))))))
(defun SCM:EnableAuto ()
  (if SCM:commands (vlr-remove SCM:commands))
  (if SCM:lisp (vlr-remove SCM:lisp))
  (setq SCM:commands (vlr-command-reactor "SINCAL marcas"
    '((:vlr-commandEnded . SCM:CommandEnded))))
  (setq SCM:lisp (vlr-lisp-reactor "SINCAL marcas"
    '((:vlr-lispEnded . SCM:LispEnded))))
  (SCM:Watch))
(defun SCM:LispEnded (reactor params)
  (if (and SCM:pending (not SCM:busy) (= 0 (getvar "BLOCKEDITOR")))
    (vl-catch-all-apply 'SCM:Sync nil)))
(defun SCM:EnableIfInteractive (/ doc)
  ;; Core Console has no ActiveDocument. Do not leave partially installed
  ;; reactors behind when this file is loaded by a non-interactive worker.
  (setq doc (vl-catch-all-apply 'SCM:Doc nil))
  (if (and (not (vl-catch-all-error-p doc)) (= (type doc) 'VLA-OBJECT))
    (SCM:EnableAuto)))
(SCM:EnableIfInteractive)
(princ "\n[SINCAL] Marcas: vinculacion automatica al confirmar XX. MARCA-SC / MARCA-DE / REASIGNAR-MARCA / ACTUALIZAR-MARCAS / REVISAR-MARCAS.")
(princ)
